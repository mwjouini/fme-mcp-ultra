FME workspace MCPAgentBridge_Demo.fmw
Title: MCPAgentBridge Demo
Description: Demo workspace demonstrating AI Agent & MCP integration with FME Form

Creator
    CREATOR_NAME = Creator
    NUM_CLONES = 5
    -> Setup_AI_Params
Setup_AI_Params: AttributeCreator
    -> MCPAgentBridge
MCPAgentBridge: PythonCaller
    NEW_ATTRIBUTES = _mcp_status _ai_action_used _ai_bridge_port _ai_response
    PYTHONSOURCE:
      # MCPAgentBridge FME Custom Transformer Script
      # Runs natively inside FME Form's embedded Python. Zero external setup.
      import contextlib
      import json
      import socket
      import sys
      import time

      try:
          import fmeobjects
      except ImportError:
          pass

      class MCPAgentBridgeTransformer:
          def __init__self:
              self.host = "127.0.0.1"
              self.port = 9877
              self.sock = None
              self.connected = False
              self._init_connection

          def _init_connectionself:
              try:
                  self.sock = socket.socketsocket.AF_INET, socket.SOCK_STREAM
                  self.sock.settimeout0.8
                  self.sock.connectself.host, self.port
                  self.connected = True
              except Exception:
                  self.connected = False
                  self.sock = None

          def inputself, feature:
              action = feature.getAttribute"_ai_action" or "INSPECT"
              feature_type =
                  feature.getFeatureType
                  if hasattrfeature, "getFeatureType"
                  else strfeature.getAttribute"fme_feature_type" or "Feature"


              attrs = {}
              if hasattrfeature, "getAllAttributeNames":
                  for name in feature.getAllAttributeNames:
                      if not name.startswith"fme_" and not name.startswith"_mcp_":
                          val = feature.getAttributename
                          if val is not None:
                              attrs[name] = strval

              payload = {
                  "jsonrpc": "2.0",
                  "method": "fme_feature_event",
                  "params": {
                      "action": action,
                      "feature_type": feature_type,
                      "attributes": attrs,
                      "timestamp": time.time,
                  },
              }

              if self.connected and self.sock:
                  try:
                      msg = json.dumpspayload + "
      ".encode"utf-8"
                      self.sock.sendallmsg
                      status = "AI_CONNECTED"
                      resp = f"Sent to AI Agent on port {self.port}"
                  except Exception as err:
                      status = f"BRIDGE_ERROR: {err}"
                      resp = "Bridge socket send error"
                      self.connected = False
              else:
                  status = "STANDALONE_FME"
                  resp = "Processed via FME Embedded Python MCP bridge ready on port 9877"

              feature.setAttribute"_mcp_status", status
              feature.setAttribute"_ai_action_used", action
              feature.setAttribute"_ai_bridge_port", self.port
              feature.setAttribute"_ai_response", resp

              if hasattrself, "pyoutput":
                  self.pyoutputfeature

          def closeself:
              if self.sock:
                  with contextlib.suppressException:
                      self.sock.close
                  self.sock = None
                  self.connected = False
    PYTHONSYMBOL = MCPAgentBridgeTransformer
